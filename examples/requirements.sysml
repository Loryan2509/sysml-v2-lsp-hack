package requirements {
    requirement def Shape {
        doc /* The system shall be a perfect cube of 1m^2. */
        
    }
    requirement def Material {
        doc /* The system shall be made of 2024 Aluminium. */
    }
    requirement def Weight {
        doc /* The system shall weigh no more than 1kg. */
    }
}
